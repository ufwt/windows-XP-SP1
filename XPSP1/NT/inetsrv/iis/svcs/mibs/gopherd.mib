GopherServer-MIB DEFINITIONS ::= BEGIN

        IMPORTS
                enterprises,
                OBJECT-TYPE,
                Counter
                        FROM RFC1155-SMI
                InternetServer
                        FROM inetsrv;

--      microsoft       OBJECT IDENTIFIER ::= { enterprises 311 }
--      software        OBJECT IDENTIFIER ::= { microsoft 1 }
--      InternetServer  OBJECT IDENTIFIER ::= { software 7 }
        GopherServer       OBJECT IDENTIFIER ::= { InternetServer 4 }
        GopherStatistics   OBJECT IDENTIFIER ::= { GopherServer 1 }

-- Gopher Server Statistics

        TotalBytesSent_HighWord OBJECT-TYPE
                SYNTAX  Counter
                ACCESS  read-only
                STATUS  mandatory
                DESCRIPTION
                        "This is the high 32-bits of the total number of
                        of BYTEs sent by the Gopher Server"
                ::= { GopherStatistics 1 }

        TotalBytesSent_LowWord OBJECT-TYPE
                SYNTAX  Counter
                ACCESS  read-only
                STATUS  mandatory
                DESCRIPTION
                        "This is the low 32-bits of the total number of
                        of BYTEs sent by the Gopher Server"
                ::= { GopherStatistics 2 }

        TotalBytesReceived_HighWord OBJECT-TYPE
                SYNTAX  Counter
                ACCESS  read-only
                STATUS  mandatory
                DESCRIPTION
                        "This is the high 32-bits of the total number of
                        of BYTEs received by the Gopher Server"
                ::= { GopherStatistics 3 }

        TotalBytesReceived_LowWord OBJECT-TYPE
                SYNTAX  Counter
                ACCESS  read-only
                STATUS  mandatory
                DESCRIPTION
                        "This is the low 32-bits of the total number of
                        of BYTEs received by the Gopher Server"
                ::= { GopherStatistics 4 }

        TotalFilesSent OBJECT-TYPE
                SYNTAX  Counter
                ACCESS  read-only
                STATUS  mandatory
                DESCRIPTION
                        "This is the total number of files sent by this
                        Gopher Server"
                ::= { GopherStatistics 5 }

        TotalDirectorySent OBJECT-TYPE
                SYNTAX  Counter
                ACCESS  read-only
                STATUS  mandatory
                DESCRIPTION
                        "This is the total number of directory listings sent
                        by this Gopher Server"

                ::= { GopherStatistics 6 }

        TotalSearchesDone OBJECT-TYPE
                SYNTAX  Counter
                ACCESS  read-only
                STATUS  mandatory
                DESCRIPTION
                        "This is the total number of searches done by this
                         Gopher Server"
                ::= { GopherStatistics 7 }

        CurrentAnonymousUsers OBJECT-TYPE
                SYNTAX  Integer
                ACCESS  read-only
                STATUS  mandatory
                DESCRIPTION
                        "This is the number of anonymous users currently
                        connected to the Gopher Server"
                ::= { GopherStatistics 8 }

        CurrentNonAnonymousUsers OBJECT-TYPE
                SYNTAX  Integer
                ACCESS  read-only
                STATUS  mandatory
                DESCRIPTION
                        "This is the number of nonanonymous users currently
                        connected to the Gopher Server"
                ::= { GopherStatistics 9 }

        TotalAnonymousUsers OBJECT-TYPE
                SYNTAX  Counter
                ACCESS  read-only
                STATUS  mandatory
                DESCRIPTION
                        "This is the total number of anonymous users that
                        have ever connected to the Gopher Server"
                ::= { GopherStatistics 10 }

        TotalNonAnonymousUsers OBJECT-TYPE
                SYNTAX  Counter
                ACCESS  read-only
                STATUS  mandatory
                DESCRIPTION
                        "This is the total number of nonanonymous users that
                        have ever connected to the Gopher Server"
                ::= { GopherStatistics 11 }

        MaxAnonymousUsers OBJECT-TYPE
                SYNTAX  Counter
                ACCESS  read-only
                STATUS  mandatory
                DESCRIPTION
                        "This is the maximum number of anonymous users
                        simultaneously connected to the Gopher Server"
                ::= { GopherStatistics 12 }

        MaxNonAnonymousUsers OBJECT-TYPE
                SYNTAX  Counter
                ACCESS  read-only
                STATUS  mandatory
                DESCRIPTION
                        "This is the maximum number of nonanonymous users
                        simultaneously connected to the Gopher Server"
                ::= { GopherStatistics 13 }

        CurrentConnections OBJECT-TYPE
                SYNTAX  Integer
                ACCESS  read-only
                STATUS  mandatory
                DESCRIPTION
                        "This is the current number of connections to the
                        Gopher Server"
                ::= { GopherStatistics 14 }

        MaxConnections OBJECT-TYPE
                SYNTAX  Counter
                ACCESS  read-only
                STATUS  mandatory
                DESCRIPTION
                        "This is the maximum number of simultaneous
                        connections to the Gopher Server"
                ::= { GopherStatistics 15 }

        ConnectionAttempts OBJECT-TYPE
                SYNTAX  Counter
                ACCESS  read-only
                STATUS  mandatory
                DESCRIPTION
                        "This is the number of connection attempts that
                        have been made to the Gopher Server"
                ::= { GopherStatistics 16 }

        LogonAttempts OBJECT-TYPE
                SYNTAX  Counter
                ACCESS  read-only
                STATUS  mandatory
                DESCRIPTION
                        "This is the number of logon attempts that have
                        been made to this Gopher Server"
                ::= { GopherStatistics 17 }

        AbortedConnections OBJECT-TYPE
                SYNTAX  Counter
                ACCESS  read-only
                STATUS  mandatory
                DESCRIPTION
                        " This is the number of aborted connections that have
                                been made to this Gopher Server"
                ::= { GopherStatistics  18 }
END
