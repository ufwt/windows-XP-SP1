--
--  Microsoft Windows
--  Copyright (C) Microsoft Corporation, 1992 - 1995.
--
--  File:       snego.asn
--
--  Contents:   Security Negotiation Definitions
--
--  Classes:
--
--  Functions:
--
--  History:    7-29-96   RichardW   Created
--





SNEGO DEFINITIONS ::=
BEGIN


MechType2 ::= OBJECT IDENTIFIER

MechTypeList2 ::= SEQUENCE OF MechType2

NegHints2 ::= SEQUENCE {
                        hintName[0] GeneralString OPTIONAL,
                        hintAddress[1] OCTET STRING OPTIONAL
                      }


NegTokenReq2 ::= SEQUENCE {
                            mechTypes[0] MechTypeList2,
                            desiredToken[1] OCTET STRING OPTIONAL,
                            negHints2[2] NegHints2 OPTIONAL
                         }

NegResult2 ::= ENUMERATED { accept2(0), reject2(1) }

NegResultList2 ::= SEQUENCE OF NegResult2

MechSpecInfo2 ::= OCTET STRING

NegTokenRep2 ::= SEQUENCE {
                                negResultList[0] NegResultList2,
                                supportedMech2[1] MechType2 OPTIONAL,
                                mechSpecInfo2[2] MechSpecInfo2 OPTIONAL
                         }

-- NegTokenSelect2 ::= SEQUENCE {
--                                supportedMech[0] MechType2 OPTIONAL,
--                                mechSpecInfo[1] MechSpecInfo2 OPTIONAL
--                            }

NegotiationToken2 ::= CHOICE {
                                negTokenReq[0] NegTokenReq2,
                                negTokenRep[1] NegTokenRep2
                            }
END
